WAVE-Schema DEFINITIONS ::=
BEGIN

  -- When saved in a file or sent over the wire, wrap the object with a
  -- type identifier
  WaveWireObject ::= EXTERNAL

  -- A set of policy statements about an Entity, potentially granting
  -- permissions or establishing facts
  WaveAttestation ::= SEQUENCE {
    tbs WaveAttestationTbs,
    -- The attestation is signed with an ephemeral signing key generated
    -- for a single use (or another signature scheme suitable for single
    -- use is permitted). The details of this signature are bound to
    -- the real attestation key inside the body but we don't reveal the
    -- attester at this layer
    outerSignature EXTERNAL
  }

  WaveAttestationTbs ::= SEQUENCE {
    -- the subject of the attestation, who is receiving permissions or
    -- having a property attested to
    subject EntityHash,
    subjectLocation Location,

    -- how this attestation revoked
    revocations SEQUENCE OF RevocationOption,
    -- extensions that are visible without any decryption of the
    -- attestation
    publicExtensions SEQUENCE OF Extension,
    -- The main content of the attestation SHOULD be encrypted using
    -- a scheme that permits provers and verifiers to decrypt it but
    -- nobody else. The result of decrypting this MUST be an
    -- AttestationBody object but depending on the context of the
    -- decryption (e.g prover vs verifier) the contents of that
    -- AttestationBody object may differ.
    body EXTERNAL
  }

  -- An arbitrary message encrypted using WAVE
  WaveEncryptedMessage ::= SEQUENCE {
    -- content: arbitrary message contents
    -- encryption algorithm: AES128
    -- key: contentsKey
    contents OCTET STRING,

    -- encrypted forms of contentsKey
    keys SEQUENCE OF EXTERNAL,

    -- Additional extension fields
    extensions SEQUENCE OF Extension
  }

  -- Irrespective of the algorithm used to encrypt the body, this
  -- is the object it contains
  AttestationBody ::= SEQUENCE {

    -- These are fields visible to both prover and verifier
    verifierBody AttestationVerifierBody,

    -- Material relating to the policy scheme that is only visible
    -- to the prover. When decoding as a verifier, this should not be
    -- visible
    proverPolicyAddendums SEQUENCE OF EXTERNAL,

    -- These are fields that contain information that should be
    -- visible to the subject of the Attestation (and perhaps
    -- chained attestation subjects) but should not be visible to those
    -- verifying this attestation as part of a proof.
    proverExtensions SEQUENCE OF Extension

  }


  -- These are fields visible to both prover and verifier
  AttestationVerifierBody ::= SEQUENCE {
    -- the creator of the DOT
    attester EntityHash,
    attesterLocation Location,

    -- the subject of the attestation, in outside...
    -- subject EntityHash,

    -- the policy domain. If omitted, the policy is global. A policy domain
    -- is an Entity that represents the scope of the attestation. The exact
    -- semantics are specific to the scheme, but there may be cross-policy
    -- behavior associated with the domain (e.g WR1 restricts visibility of
    -- attribute sets to those already having some grant in the domain).
    -- in some policy schemes the domain is the root of trust
    -- domain EntityHash OPTIONAL,

    -- the visibility partition. The exact semantics are specific to the
    -- scheme but there may be some cross-policy behavior associated
    -- with the partition (e.g WR1 only allows the verifier body to
    -- be decrypted by those having the key associated with the Partition
    -- or some subkey). If the sequence is length zero,
    -- partition SEQUENCE OF OCTET STRING,

    -- when is this trust valid
    validity SEQUENCE {
      notBefore UTCTime,
      notAfter UTCTime
    },

    -- the nature of the trust
    policy EXTERNAL,

    -- extensions for use by the verifier
    extensions SEQUENCE OF Extension,

    -- binding that proves that the outer signature is made by the same
    -- key that the source used (the ephemeral keys have not been switched)
    outerSignatureBinding EXTERNAL
  }

  Extension ::= SEQUENCE {
    extnID OBJECT IDENTIFIER,
    -- should parsing of the object fail if this extension is not understood
    critical BOOLEAN,
    -- DER encoding of ASN.1 value identified by extnID
    value OCTET STRING
  }

  RevocationOption ::= SEQUENCE {
    -- If this revocation scheme is not understood, should
    -- the object be treated as revoked (TRUE) or not (FALSE)
    critical BOOLEAN,
    scheme EXTERNAL
  }

  WaveEntity ::= SEQUENCE {
    tbs WaveEntityTbs,
    -- the algorithm is determined by the type of
    -- verifyingKey
    signature OCTET STRING
  }

  WaveEntityTbs ::= SEQUENCE {
    -- the canonical certification and attestation key. This is what is used
    -- to sign attestation outerSignatureBindings, and to sign this object
    verifyingKey EntityPublicKey,
    -- other public keys
    keys SEQUENCE OF EntityPublicKey,
    -- when is this entity valid
    validity SEQUENCE {
      notBefore UTCTime,
      notAfter UTCTime
    },
    -- revocations
    revocations SEQUENCE OF RevocationOption,
    -- extensions
    extensions SEQUENCE OF Extension
  }

  WaveEntitySecret ::= SEQUENCE {
    entity WaveEntity,

    keyring EXTERNAL
  }

  EntityKeyring ::= SEQUENCE {
    keys SEQUENCE OF EntityKeyringEntry
  }

  EntityKeyringEntry ::= SEQUENCE {
    public EntityPublicKey,
    secret EntityPrivateKey
  }

  BN256OAQUEKeyringBundle ::= SEQUENCE {
    params Params-BN256-OAQUE,
    entries SEQUENCE OF BN256OAQUEBundleEntry
  }

  BN256OAQUEBundleEntry ::= SEQUENCE {
    partitionChange SEQUENCE OF SEQUENCE {
      index INTEGER,
      content OCTET STRING
    },
    key Private-BN256-OAQUE
  }

  EntityPrivateKey ::= EXTERNAL

  EntityPublicKey ::= SEQUENCE {
    capabilityFlags SET OF Capability,
    key EXTERNAL
  }

  Capability ::= INTEGER {
    -- signing other keys
    certification      (1),
    -- signing attestations
    attestation        (2),
    -- signing messages or other content
    signing            (3),
    -- signing challenges that reveal ID
    authentication     (4),
    -- signing challenges that prove authorization (not via identity)
    authorization      (5),
    --
    encryption         (6)
  }

  -- there are different kinds of proofs, this represents just one, the
  -- explicit proof that reveals the attestations. The final authorization
  -- or truth conveyed is the union of the paths through the given set of
  -- attestations
  WaveExplicitProof ::= SEQUENCE {
    attestations SEQUENCE OF AttestationReference,
    -- this is a chain of attestations connected end-to-end
    -- that represent a path through the subset of the authorization
    -- graph given in the attestations field. The integer references
    -- an attestation inside the parent object
    paths SEQUENCE OF SEQUENCE OF INTEGER,
    -- optionally, entities the sender thinks the receiver won't be
    -- able to resolve can be included here (DER encoded)
    entities SEQUENCE OF OCTET STRING,
    extensions SEQUENCE OF Extension
  }



  AttestationReference ::= SEQUENCE {
    -- the hash of the WaveAttestation
    hash AttestationHash,

    -- generally the attestation is put in here verbatim
    content [0] OCTET STRING OPTIONAL,

    -- or a location is given that permits retrieving the attestation
    location [1] SEQUENCE OF Location,

    -- the content will generally need some keys to decrypt
    keys [2] SEQUENCE OF AttestationVerifierKey,

    -- for some revocation schemes, it may be necessary to submit
    -- additional information with the attestation reference that shows
    -- that the attestation is not revoked (such as a signed object by
    -- the locations in the revocation option)
    revocationChecks [3] SEQUENCE OF RevocationCheck,

    extensions [4] SEQUENCE OF Extension
  }

  RTreePolicy ::= SEQUENCE {
    -- the namespace, common to all statements. This also becomes the
    -- WR1 domain for visibility control if wr1 is used
    namespace EntityHash,
    namespaceLocation Location,
    -- specifically for use with WR1, this controls who can see the
    -- attestation
    -- this is a virtual field, there must exist some function
    -- partition but we don't store the partition
    -- partition SEQUENCE OF OCTET STRING OPTIONAL,

    -- Similar to bosswave TTL, how many times can this be redelegated
    indirections INTEGER,
    statements SEQUENCE OF RTreeStatement
  }

  RTreeStatement ::= SEQUENCE {
    permissionSet EntityHash,
    permissions SEQUENCE OF UTF8String,
    resource UTF8String,
    comment UTF8String OPTIONAL
  }

  -- A key specifically to enable a verifier to inspect a subset of an attestation
  -- for the purposes of verifying a proof
  AttestationVerifierKey ::= EXTERNAL

  -- A mini proof that a revocation does not exist
  RevocationCheck ::= EXTERNAL


  Hash ::= EXTERNAL
  EntityHash ::= Hash
  AttestationHash ::= Hash
  -- The three currently supported hash schemes
  HashSha3-256 ::= OCTET STRING
  HashSha-256 ::= OCTET STRING
  HashKeccak-256 ::= OCTET STRING

  -- When referencing an attestation or entity hash, where should this be
  -- resolvable
  Location ::= EXTERNAL

  -- this object will be DER encoded and present in the location.value scheme
  -- when the scheme is location-scheme-url
  LocationURL ::= SEQUENCE {
    value UTF8String,
    apiVersion INTEGER
  }

  -- this object will be DER encoded and present in the location.value scheme
  -- when the scheme is location-scheme-ethereum-blockchain
  LocationEthereum ::= SEQUENCE {
    chainID INTEGER,
    contractAddress INTEGER
  }

  -- A pre-shared-key attestation body ciphertext
  PSKBodyCiphertext ::= SEQUENCE {
    -- when decrypted results in the DER of an AttestationBody
    attestationBodyCiphertext OCTET STRING,
    -- the key used for encryption (which also conveys the scheme)
    encryptedUnder  EntityPublicKey
  }

  WaveNameDeclaration ::= SEQUENCE {
    tbs SEQUENCE {
      attester EntityHash,
      attesterLocation Location,
      revocations SEQUENCE OF RevocationOption,
      publicExtensions SEQUENCE OF Extension,
      -- content: NameDeclarationBody
      -- encryption algorithm: AES128
      -- encryption key: bodyKey
      body OCTET STRING,
      keys SEQUENCE OF NameDeclarationKey
    },
    signature OCTET STRING
  }

  NameDeclarationKey ::= EXTERNAL

  NameDeclarationBody ::= SEQUENCE {
    name UTF8String,
    subject EntityHash,
    subjectLocation Location,
    validity SEQUENCE {
      notBefore UTCTime,
      notAfter UTCTime
    },
    privateExtensions SEQUENCE OF Extension
  }

  -- empty sequence, the body is then just DER encoded
  NameDeclarationKeyNone ::= SEQUENCE {

  }

  NameDeclarationKeyWR1 ::= SEQUENCE {
    -- content: MessageKeyWR1Envelope DER encoded
    -- encryption algorithm: AES128
    -- encryption key: envelopeKey
    envelope OCTET STRING,

    -- content envelopeKey
    -- encryption algorithm: IBE-bn256 in declaration namespace system
    -- id: envelopeID (namespace)
    envelopeKey-ibe-bn256 OCTET STRING,

    namespace EntityHash,
    namespaceLocation Location
  }

  NameDeclarationWR1Envelope ::= SEQUENCE {
    partition SEQUENCE OF OCTET STRING,
    -- content: bodyKey
    -- encryption algorithm: oaque-bn256
    -- encryption id: partition
    bodyKey OCTET STRING
  }

  -- A body ciphertext for the wave reference 1 scheme
  WR1BodyCiphertext ::= SEQUENCE {
    -- content: WR1VerifierBody DER encoded
    -- encryption algorithm: AES128
    -- key: verifierBodyKey
    verifierBodyCiphertext OCTET STRING,

    -- content: WR1ProverBody DER encoded
    -- encryption algorithm: AES128
    -- key: proverBodyKey
    proverBodyCiphertext OCTET STRING,

    -- content WR1Envelope DER encoded
    -- encryption algorithm: AES128
    -- key: envelopeKey
    envelopeCiphertext OCTET STRING,

    -- content envelopeBodyKey
    -- encryption algorithm: IBE-bn256 in subject system
    -- id: envelopeID (namespace)
    envelopeKey-ibe-bn256 OCTET STRING,

    -- content envelopeBodyKey
    -- encryption algorithm: AES128
    -- key: ECDH (outer signature key, subject key)
    -- this permits reading the envelope if you are the direct
    -- recipient, even without knowing the namespace
    envelopeKey-curve25519 OCTET STRING,

    -- content prover/verifierBodyKeys	
    -- encryption algorithm: AES128	
    -- key: ECDH (outer signature key, attester key)	
    -- this permits reading the attestation if you are the attester	
    -- even without knowing the namespace	
    envelopeKey-curve25519-attester OCTET STRING
  }

  WR1Envelope ::= SEQUENCE {
    -- content: proverBodyKey || proverBodyNonce || verifierBodyKey || verifierBodyNonce
    -- encryption algorithm: oaque-bn256 in subject system
    -- encryption attribute set: Partition
    bodyKeys-oaque OCTET STRING,

    -- the attribute set for the verifierBodyKey-oaque ciphertext
    partition SEQUENCE OF OCTET STRING
  }

  WR1ProverBody ::= SEQUENCE {
    --which keys do we give other people
    --we have PartitionKeys that reveal the content
    --we have a Domain Key that reveals the partition attribute set
    addendums SEQUENCE OF EXTERNAL,

    extensions SEQUENCE OF Extension
  }

  WR1VerifierBody ::= SEQUENCE {
    attestationVerifierBody AttestationVerifierBody
  }

  Ed25519OuterSignature ::= SEQUENCE {
    verifyingKey OCTET STRING,
    signature OCTET STRING
  }

  Signature ::= SEQUENCE {
    -- use the key scheme as an identifier
    scheme OBJECT IDENTIFIER,
    signature OCTET STRING
  }

  SignedOuterKey ::= SEQUENCE {
    tbs SignedOuterKeyTbs,
    signature OCTET STRING
  }

  SignedOuterKeyTbs ::= SEQUENCE {
    outerSignatureScheme OBJECT IDENTIFIER,
    verifyingKey OCTET STRING
  }

  TrustLevel ::= SEQUENCE {
    trust INTEGER (1..4)
  }

  CommitmentRevocationOption ::= SEQUENCE {
    -- What the commitment should hash to
    hash Hash,
    -- Where to look for it
    location Location
  }

  AVKeyAES128-GCM ::= OCTET STRING

  Private-Ed25519 ::= OCTET STRING
  Private-Curve25519 ::= OCTET STRING
  Private-BN256-OAQUE ::= OCTET STRING
  Private-BN256-IBE ::= OCTET STRING
  Master-BN256-OAQUE ::= OCTET STRING
  Master-BN256-IBE ::= OCTET STRING
  Public-Ed25519 ::= OCTET STRING
  Public-Curve25519 ::= OCTET STRING
  Public-OAQUE ::= SEQUENCE {
    params Params-BN256-OAQUE,
    attributeset SEQUENCE OF OCTET STRING
  }
  Params-BN256-OAQUE ::= OCTET STRING
  Params-BN256-IBE ::= OCTET STRING
  Public-BN256-IBE ::= SEQUENCE {
    params Params-BN256-IBE,
    id OCTET STRING
  }
  -- Encapsulates parameters to PBKDF2. Sha3-512 is assumed as the hash function
  -- in this particular scheme
  KeyringAESCiphertext ::= SEQUENCE {
    ciphertext OCTET STRING,
    salt OCTET STRING,
    iterations INTEGER
  }

  MessageKeyCurve25519ECDH ::= SEQUENCE {
    ciphertext OCTET STRING
  }

  MessageKeyWR1 ::= SEQUENCE {
    -- content: MessageKeyWR1Envelope DER encoded
    -- encryption algorithm: AES128
    -- encryption key: envelopeKey
    envelope OCTET STRING,

    -- content envelopeKey
    -- encryption algorithm: IBE-bn256 in message namespace system
    -- id: envelopeID (namespace)
    envelopeKey-ibe-bn256 OCTET STRING,

    -- the system for the keys
    namespace EntityHash,
    namespaceLocation Location
  }

  MessageKeyWR1Envelope ::= SEQUENCE {
    partition SEQUENCE OF OCTET STRING,
    -- content: contentsKey
    -- encryption algorithm: oaque-bn256
    -- encryption id: partition,
    contentsKey OCTET STRING
  }

END
